#!/usr/bin/env python
# -*- coding: utf-8 -*-

# ====================================================================================
# ====================================================================================
# ==                                                                                ==
# ==                               Simple grid                                      ==
# ==                                                                                ==
# == Updated Simple Grid to allow modification to include major lines and also to   ==
# == display the total grid size for reference.                                     ==
# ==                                                                                ==
# ====================================================================================
# ====================================================================================
# ABOUT
# ====================================================================================
# version v1.0
# Macro developed for FreeCAD (http://www.freecadweb.org/).
# This macro toggles a configurable grid in plane XY as helper for 3D view navigation
#
# LICENSE
# ====================================================================================
# Copyright (c) 2019 Pablo Gil Fernandez
#
# This work is licensed under GNU Lesser General Public License (LGPL).
# To view a copy of this license, visit https://www.gnu.org/licenses/lgpl-3.0.html
#
# MODIFICATIONS
# ====================================================================================
# Version 2.0 - Kevin Hill
# This code has been modified under the instructions of Kevin Hill on 2025-06-23.
# The modifications were generated by GPT-40 and include the following:
# - Ensured size_x and size_y are evenly divisible by major_line intervals (`major_line_every_x` and `major_line_every_y`), rounding up.
# - Added a title to the top of the grid with a font size proportionate to the grid size (`size_x / 50`) indicating the size of the grid as `mm x mm`.
# - Ensured the title is added under the "Grid" folder being created.
# - Created a style for the text object to ensure the font size command works properly.
# - Fixed centering of the text by adjusting its `Placement` property.
# ====================================================================================
__title__   = "Simple grid"
__author__  = "Pablo Gil Fernández"
__version__ = "1.0"
__date__    = "11/08/2019"

__author__  = "Kevin Hill"
__version__ = "2.0"
__date__    = "06/22/2025"

__Comment__ = "This macro toggles a configurable grid in plane XY as helper for 3D view navigation."

__Wiki__ = "https://www.freecadweb.org/wiki/Simple_grid"
__Help__ = ""
__Status__ = "stable"
__Requires__ = "freecad 0.99"

import FreeCAD, FreeCADGui, Draft
from math import ceil
from PySide import QtGui # for clearing the console

def a_clear_console():
    #clearing previous messages
    mw=FreeCADGui.getMainWindow()
    r=mw.findChild(QtGui.QTextEdit, "Report view")
    r.clear()

a_clear_console()

# Retrieve Draft preferences ====================================
draft_prefs = FreeCAD.ParamGet("User parameter:BaseApp/Preferences/Mod/Draft")

# Variables ====================================
spacing_x = draft_prefs.GetFloat("gridSpacing", 10)  # Default 10 if not set
spacing_y = spacing_x  # Grid spacing is uniform
major_line_every_x = draft_prefs.GetInt("gridSize", 5)  # Default 5 if not set
major_line_every_y = major_line_every_x

# Ensure size_x and size_y are evenly divisible by major_line intervals, rounding up
size_x = ceil(1000 / (major_line_every_x * spacing_x)) * (major_line_every_x * spacing_x)
size_y = ceil(1000 / (major_line_every_y * spacing_y)) * (major_line_every_y * spacing_y)

# Colors ====================================
line_color = draft_prefs.GetString("gridLineColor", "0.5,0.5,0.5").split(",")
x_axis_color = draft_prefs.GetString("gridAxisColor", "0.7,0,0").split(",")
y_axis_color = draft_prefs.GetString("gridAxisColor", "0,0.7,0").split(",")
x_axis_major_color = draft_prefs.GetString("gridMajorLineColor", "0.8,0.2,0.2").split(",")
y_axis_major_color = draft_prefs.GetString("gridMajorLineColor", "0.2,0.8,0.2").split(",")

line_color = tuple(map(float, line_color))
x_axis_color = tuple(map(float, x_axis_color))
y_axis_color = tuple(map(float, y_axis_color))
x_axis_major_color = tuple(map(float, x_axis_major_color))
y_axis_major_color = tuple(map(float, y_axis_major_color))

line_width = 0.5  # Adjusted line width
axis_width = line_width * 2
major_line_width = line_width * 1.5  # Width of major lines
text_color_bright_green = (0.0, 1.0, 0.0)  # Bright green for titles

globalAxisCross = False
groupName = 'Grid'

# Main toggle ====================================
if len(App.ActiveDocument.getObjectsByLabel(groupName)) == 0: # if grid doesn't exist create it
    # Create the grid group
    grid_group = App.ActiveDocument.addObject("App::DocumentObjectGroup", groupName)

    # Global document axis ====================================
    Gui.ActiveDocument.ActiveView.setAxisCross(globalAxisCross)

    pl = FreeCAD.Placement()
    pl.Rotation.Q = (0.0, 0.0, 0.0, 1.0)

    # Lines step correction ====================================
    lines_x = int(size_x / spacing_x)
    center_x = int(lines_x / 2) + 1
    if lines_x % 2 == 0:
        lines_x += 1  # if number of lines is even it must change to odd
    lines_y = int(size_y / spacing_y)
    center_y = int(lines_y / 2) + 1
    if lines_y % 2 == 0:
        lines_y += 1  # if number of lines is even it must change to odd

    # X secondary lines ====================================
    i = 1
    while i <= lines_x:
        from_vector = FreeCAD.Vector(-(lines_y - 1) * spacing_y / 2, (i - 1) * spacing_x - (lines_x - center_x) * spacing_x, 0.0)
        to_vector = FreeCAD.Vector((lines_y - 1) * spacing_y / 2, (i - 1) * spacing_x - (lines_x - center_x) * spacing_x, 0.0)
        pl.Base = from_vector
        points = [pl.Base, to_vector]
        line = Draft.makeWire(points, placement=pl, closed=False, face=True, support=None)
        line.Label = "xline_" + str(i)

        # Check if this is a major line
        if (i - center_x) % major_line_every_x == 0:
            line_width_current = major_line_width
            line_color_current = x_axis_major_color
        elif i == center_x:
            line_width_current = axis_width
            line_color_current = x_axis_color
        else:
            line_width_current = line_width
            line_color_current = line_color

        App.ActiveDocument.getObjectsByLabel(line.Label)[0].ViewObject.LineWidth = line_width_current
        App.ActiveDocument.getObjectsByLabel(line.Label)[0].ViewObject.LineColor = line_color_current
        App.ActiveDocument.getObjectsByLabel(line.Label)[0].ViewObject.PointColor = line_color_current
        App.ActiveDocument.getObjectsByLabel(line.Label)[0].ViewObject.Selectable = False
        grid_group.addObject(App.ActiveDocument.getObjectsByLabel(line.Label)[0])
        i += 1

    # Y secondary lines ====================================
    i = 1
    while i <= lines_y:
        from_vector = FreeCAD.Vector((i - 1) * spacing_y - (lines_y - center_y) * spacing_y, -(lines_x - 1) * spacing_x / 2, 0.0)
        to_vector = FreeCAD.Vector((i - 1) * spacing_y - (lines_y - center_y) * spacing_y, (lines_x - 1) * spacing_x / 2, 0.0)
        pl.Base = from_vector
        points = [pl.Base, to_vector]
        line = Draft.makeWire(points, placement=pl, closed=False, face=True, support=None)
        line.Label = "yline_" + str(i)

        # Check if this is a major line
        if (i - center_y) % major_line_every_y == 0:
            line_width_current = major_line_width
            line_color_current = y_axis_major_color
        elif i == center_y:
            line_width_current = axis_width
            line_color_current = y_axis_color
        else:
            line_width_current = line_width
            line_color_current = line_color

        App.ActiveDocument.getObjectsByLabel(line.Label)[0].ViewObject.LineWidth = line_width_current
        App.ActiveDocument.getObjectsByLabel(line.Label)[0].ViewObject.LineColor = line_color_current
        App.ActiveDocument.getObjectsByLabel(line.Label)[0].ViewObject.PointColor = line_color_current
        App.ActiveDocument.getObjectsByLabel(line.Label)[0].ViewObject.Selectable = False
        grid_group.addObject(App.ActiveDocument.getObjectsByLabel(line.Label)[0])
        i += 1

    # Text annotations ====================================
    font_size = size_x / 40  # Font size based on total width

    # Main title: Top of the grid indicating grid size in mm x mm format
    grid_title_text = Draft.make_text([f"Grid Size:\n{size_x} mm x {size_y} mm"], FreeCAD.Vector(size_x / 2, size_y / 2 + 20, 0))
    grid_title_text.ViewObject.FontName = "Sans"
    grid_title_text.ViewObject.FontSize = font_size
    grid_title_text.ViewObject.TextColor = text_color_bright_green
    grid_title_text.Label = 'Grid Title Text' 
    grid_group.addObject(grid_title_text)  # Add text to Grid group object

    # Finalize ====================================
    FreeCAD.ActiveDocument.recompute()
    Gui.ActiveDocument.getObject(groupName).Visibility = False  # trick to hide it at the first try in the Model hierarchy
    Gui.ActiveDocument.getObject(groupName).Visibility = True   # trick to hide it at the first try in the Model hierarchy

    print("Grid enabled: a " + str(int((lines_x - 1) * spacing_x)) + "x" + str(int((lines_y - 1) * spacing_y)) + " grid has successfully been created")
else:
    App.ActiveDocument.getObject(groupName).removeObjectsFromDocument()
    App.ActiveDocument.removeObject(groupName)
    print("Grid disabled")
